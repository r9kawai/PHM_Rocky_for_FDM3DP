# Auto export .stl format file for 3d print parts.
import FreeCAD as App, Part

doc = App.ActiveDocument
docfile_ = doc.Name
#print(docfile_)

docfile = docfile_ + '.FCStd'
outpath = './exportSTL/'

bodylabel_exname_list = [
    ['rocky_torso_up',        '01_rocky_torso_up',     'Y',  0],
    ['rocky_torso_bottom',    '02_rocky_torso_bottom', 'X',  2],
    ['dowel_pin_1',           '03_dowel_pin_1',        'Y',  1],
    ['dowel_pin_2',           '03_dowel_pin_2',        'Y',  1],
    ['dowel_pin_3',           '03_dowel_pin_3',        'Y',  1],
    ['rocky_1-A',             '04_rocky_1-A',          'Y',  0],
    ['rocky_1-C',             '05_rocky_1-C',          'Y',  0],
    ['rocky_2-A',             '06_rocky_2-A',          'Y',  0],
    ['rocky_2-B',             '07_rocky_2-B',          'Y',  0],
    ['rocky_3-A',             '08_rocky_3-A',          'Y',  0],
    ['rocky_3-B',             '09_rocky_3-B',          'Y',  0],
    ['rocky_4-A',             '10_rocky_4-A',          'Y',  0],
    ['rocky_4-B',             '11_rocky_4-B',          'Y',  0],
    ['rocky_5-A',             '12_rocky_5-A',          'Y',  0],
    ['rocky_5-B',             '13_rocky_5-B',          'Y',  0],
]

def export_body_rot90_stl(doc_path: str,
                           body_label: str,
                           stl_path: str,
                           axis: str = 'Z',
                           quarters: int = 1) -> None:
    # ---------- 1. ドキュメント取得 ----------
    if not os.path.isfile(doc_path):
        raise FileNotFoundError(doc_path)

    # 既に開いていれば再利用
    doc = next((d for d in App.listDocuments().values()
                if os.path.abspath(d.FileName) == os.path.abspath(doc_path)),
               None) or App.openDocument(doc_path)

    # ---------- 2. Body をラベル名で取得 ----------
    try:
        body = next(obj for obj in doc.getObjectsByLabel(body_label)
                    if obj.TypeId == "PartDesign::Body")
    except StopIteration:
        raise LookupError(f"Body '{body_label}' not found")

    # ---------- 2.1 取得した Body の形状チェック ----------
    ok = body.Shape.isValid()
    if ok:
        report = body.Shape.check()
        if not report:
            print("check OK", end="")
        else:
            raise LookupError(f"Body '{body_label}' is Geometry error")
    else:
        raise LookupError(f"Body '{body_label}' is Geometry error")

    # ---------- 3. 形状コピー → 回転 ----------
    shp = body.Shape.copy()                           # オリジナルは無傷
    axis_vec = {'X': App.Vector(1,0,0),
                'Y': App.Vector(0,1,0),
                'Z': App.Vector(0,0,1)}[axis.upper()]
    angle = 90 * quarters                             # 90°×n
    shp.rotate(App.Vector(0,0,0), axis_vec, angle)    # 原点回り

    # ---------- 4. STL 出力 ----------
    shp.exportStl(stl_path)
    print(f" {stl_path}")

if __name__ == "__main__":
    print(f"From {docfile} To {outpath} ...")
    for bodylabel_exname in bodylabel_exname_list:
        bodylabel = bodylabel_exname[0]
        exname = bodylabel_exname[1]
        axis = bodylabel_exname[2]
        quarters = bodylabel_exname[3] 
        expath = outpath + exname + '.stl'
        export_body_rot90_stl(docfile, bodylabel, expath, axis, quarters)
    print('Macro done')
